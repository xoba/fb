// A tiny catalog of example files.
module example-catalog {
  yang-version 1.1;
  namespace "https://example.com/ns/catalog";
  prefix cat;

  organization "Example";
  description "A tiny in-memory catalog of example files.";

  revision 2026-11-10 {
    description "Initial revision.";
  }

  container catalog {
    list file {
      key "name";
      leaf name {
        type string;
      }
      leaf bytes {
        type uint64;
        units "bytes";
      }
    }
  }
}
